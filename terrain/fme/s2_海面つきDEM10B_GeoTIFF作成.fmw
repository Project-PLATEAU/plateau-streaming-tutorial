FME workspace s2_海面つきDEM10B_GeoTIFF作成.fmw

Parameters:
- DestDataset_GEOTIFF =
- SourceDataset_PATH =

Readers:
- PATH_1: PATH from $(SourceDataset_PATH)

Writers:
- GEOTIFF_1: GEOTIFF to $(DestDataset_GEOTIFF)
- FILECOPY_1: FILECOPY to $(DestDataset_GEOTIFF)

Note: dem10: [PATH]
PATH (reader PATH_1)
    attributes: path_unix buffer, path_windows buffer, path_rootname buffer, path_filename buffer, path_extension buffer, path_filesize number(20,0), path_ownername buffer, path_readonly logical, path_modified_date datetime, path_created_date datetime, path_accessed_date datetime, path_directory_unix buffer, path_directory_windows buffer, path_type char(10)
    -> FeatureReader [INITIATOR]
FeatureReader
    ATTRIBUTES = GEOTIFF,"fme_basename,fme_dataset"
    ATTR_ACCUM_MODE = Only Use Result
    COMBINE_GEOM = Use Result
    DATASET = @Value(path_unix)
    FORMAT = GEOTIFF
    GEOTIFF_APPLY_GCPS = NO
    GEOTIFF_FEATURE_TYPE_NAME = FORMAT_NAME
    GEOTIFF_GEOTIFF_EXPOSE_FORMAT_ATTRS = fme_basename,char(50) fme_dataset,char(50)
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = NONE
    OUTPUT_FEATURES_DISPLAY = Schema and Data Features
    GEOTIFF -> StringSearcher
StringSearcher
    CASE = no
    MATCHED_RESULT_ATTR = _meshcode
    REGEXP = \d{4}-\d{2}
    STRING_TO_SEARCH = @Value(fme_basename)
    MATCHED -> RasterExtractor
RasterExtractor
    RASTER_BLOB_ATTR = _rasterBlob
    RASTER_FORMAT = GEOTIFF
    RASTER_FORMAT_ATTR = _rasterFormatName
    -> RasterBandNodataRemover
RasterBandNodataRemover
    -> RasterBandMinMaxExtractor
RasterBandMinMaxExtractor
    -> RasterExtentsCoercer
RasterExtentsCoercer
    EXTENTS_TYPE = Raster Extents
    EXTENTS -> Tester
    EXTENTS -> AttributeKeeper
AttributeKeeper
    CREATE_BULK_MODE_FEATURES = NO
    -> Clipper [CLIPPER]
Tester
    BOOL_OP = OR
    COMPOSITE_TEST = 1
    TEST_CLAUSE = TEST -9000 < @Value(_band{0}.min)
    TEST_MODE = TEST
    PASSED -> AttributeManager_2
    FAILED -> Junction
AttributeManager_2
    ATTR_TABLE:
      REMOVE fme_basename
      RENAME_SET_VALUE fme_dataset > filecopy_source_dataset
      SET_TO filecopy_dest_filename = @Value(_meshcode).tif
      REMOVE _rasterFormatName
      REMOVE _rasterBlob
      REMOVE _band{}.min
      REMOVE _band{}.max
      REMOVE _band{}.palette{}.keyMin
      REMOVE _band{}.palette{}.keyMax
      REMOVE _band{}.palette{}.valueMin
      REMOVE _band{}.palette{}.valueMax
      REMOVE _meshcode
    -> . (writer FILECOPY_1)
. (writer FILECOPY_1)
Junction
    -> Scaler
    -> RasterReplacer_2
Scaler
    RASTER_SCALING = Extents
    SCALE_ORIGIN = Center Point
    TEXT_LOC_ONLY = Location and Size
    XSCALE = 5
    YSCALE = 5
    ZSCALE = 1
    SCALED -> Tiler
Tiler
    BOUNDARY_CASES = No
    CLEANING_TOLERANCE = Automatic
    COL_ATTR = _column
    GROUP_BY = fme_basename
    LINES_AS_SEGMENTS = No
    MEASURE_TYPE = Continuous
    MISSING_VAL_MODE = Compute
    NUM_HORIZONTAL_TILES = 5
    NUM_VERTICAL_TILES = 5
    ROW_ATTR = _row
    STARTINGCORNER = Lower Left
    TILING_TYPE = Number of Tiles
    TILED -> CenterPointReplacer
CenterPointReplacer
    POINTTYPE = CENTER
    POINT -> JpMeshCodeExtractor
JpMeshCodeExtractor
    DELIMITER = -
    MESHCODE_ATTR = _meshcode
    MESH_TYPE = 2
    -> DuplicateFilter
DuplicateFilter
    INPUT_ORDERED_CHOICE = No
    KEYATTR = _meshcode
    UNIQUE -> Clipper [CLIPPEE]
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    OUTSIDE -> JpMeshCodeReplacer
JpMeshCodeReplacer
    CREATE_ONE_TENTH_SUBMESH = No
    GEOM_TYPE = Polygon
    MESHCODE_ATTR = _meshcode
    MESHTYPE_ATTR = _meshtype
    -> 3DForcer
3DForcer
    KEEPZVAL = No
    ZVALATTR = 0
    -> BoundsExtractor
BoundsExtractor
    XMAX = _xmax
    XMIN = _xmin
    YMAX = _ymax
    YMIN = _ymin
    -> AttributeManager
AttributeManager
    ATTR_TABLE:
      REMOVE _band{}.min
      REMOVE _band{}.max
      REMOVE _band{}.palette{}.keyMin
      REMOVE _band{}.palette{}.keyMax
      REMOVE _band{}.palette{}.valueMin
      REMOVE _band{}.palette{}.valueMax
      REMOVE _clipped
      REMOVE _fme_no_clipper
      REMOVE _meshtype
      REMOVE fme_basename
    USER_EXPOSED_ATTRIBUTES = _overlaps
    -> FeatureMerger [REQUESTOR]
RasterReplacer_2
    BLOB_ATTR = _rasterBlob
    FORMAT = GEOTIFF
    REMOVE_ATTRIBUTE = Yes
    -> RasterBandNodataSetter
RasterBandNodataSetter
    NODATA_VALUE = 0
    REPLACE_CELL_VALUES = Yes
    -> RasterBandNodataSetter_2
RasterBandNodataSetter_2
    NODATA_VALUE = -9999
    REPLACE_CELL_VALUES = No
    -> Junction_2
Junction_2
    -> Junction_4
Note: RasterBandNodataSetter_2 : Output
Junction_4
    -> Raster1 (writer GEOTIFF_1)
RasterNumericCreator
    CELL_ELEMENT_TYPE = Real32
    HEIGHT = 750
    MAX_NUMERIC_VALUE = 0
    MIN_NUMERIC_VALUE = 0
    RASTER_TYPE_PARAM = Single Value
    ROTATION = 0.0
    ROWCOL_OR_CELLSIZE = RowsColumns
    WIDTH = 1125
    X_CELL_ORIGIN = 0.5
    X_SPACING = 1.0
    X_UPPER_LEFT_COORD = 0.0
    Y_CELL_ORIGIN = 0.5
    Y_SPACING = 1.0
    Y_UPPER_LEFT_COORD = 0.0
    CREATED -> FeatureMerger [SUPPLIER]
FeatureMerger
    JOIN_KEYS = 1 1 AUTO
    MERGE_TYPE = Geometry
    PROCESS_DUPS = NO
    REJECT_NULL_MISSING_KEYS = No
    SUPPLIERS_FIRST = Yes
    MERGED -> RasterGeoreferencer
RasterGeoreferencer
    POINTANDANGLE_OR_EXTENTS = Extents
    X_LL_COORD = @Value(_xmin)
    X_LR_COORD = @Value(_xmax)
    X_UL_COORD = @Value(_xmin)
    X_UR_COORD = @Value(_xmax)
    Y_LL_COORD = @Value(_ymin)
    Y_LR_COORD = @Value(_ymin)
    Y_UL_COORD = @Value(_ymax)
    Y_UR_COORD = @Value(_ymax)
    -> CoordinateSystemSetter
CoordinateSystemSetter
    COORDSYS = EPSG:6668
    -> Raster1 (writer GEOTIFF_1)
Raster1 (writer GEOTIFF_1)

FME custom transformer JpMeshCodeExtractor
Extracts Japanese Standard Mesh Code of the mesh containing the first coordinate of the input feature. 
    If the input feature doesn't have coordinates, it will be output from the <Rejected> port. 
    Notes:
    This transformer is valid only for a geographic data on Japanese area with LL coordinate system.
    This transformer rounds the coordinate values into milliseconds when computing mesh code. So an computational error may not be avoided if the coordinate is very close to a mesh boundary.
    This transformer supports these Japanese standard mesh types.
    Primary Standard Mesh - spacing (W x H): 3600sec. x 2400sec., mesh code format: "AABB"
    Secondary Standard Mesh - spacing (W x H): 450sec. x 300sec., mesh code format: "AABB-CD"
    Tertiary Standard Mesh - spacing (W x H): 45sec. x 30sec., mesh code format: "AABB-CD-EF"
    1/2 Subdivided Mesh - spacing (W x H): 22.5sec. x 15sec., mesh code format: "AABB-CD-EF-G"
    1/4 Subdivided Mesh - spacing (W x H): 11.25sec. x 7.5sec., mesh code format: "AABB-CD-EF-G-H" 
    1/8 Subdivided Mesh - spacing (W x H): 5.625sec. x 3.75sec., mesh code format: "AABB-CD-EF-G-H-I"
    1/10 Subdivided Mesh - spacing (W x H): 4.5sec. x 3sec., mesh code format: "AABB-CD-EF-XY
    A - I, X and Y in the formats represents a digit determined by the followings.
    AA = south end latitude (degrees) of the primary mesh * 1.5
    BB = west end longitude (degrees) of the primary mesh - 100
    C = row index in the parent primary mesh (0:south - 7:north end)
    D = column index in the parent primary mesh (0:west - 7:east end)
    E = row index in the parent secondary mesh (0:south - 9:north end)
    F = column index in the parent secondary mesh (0:west - 9:east end)
    G = 1:left-bottom, 2:right-bottom, 3:left-top, 4:right-top in the parent tertiary mesh
    H = 
    1:left-bottom, 2:right-bottom, 3:left-top, 4:right-top in the parent 1/2 subdivided mesh
    I = 
    1:left-bottom, 2:right-bottom, 3:left-top, 4:right-top in the parent 1/4 subdivided mesh
    X = row index in the parent tertiary mesh (0:south - 9:north end)
    Y = column index in the parent tertiary mesh (0:west - 9:east end)
Parameters
    Mesh Type:
    Choose the mesh type.
    -----
    Primary Standard Mesh
    Secondary Standard Mesh
    Tertiary Standard Mesh
    1/2 Subdivided Mesh
    1/4 Subdivided Mesh
    1/8 Subdivided Mesh
    1/10 Subdivided Mesh
    -----
    Mesh Code Attribute:
    Specify an attribute name which will store the mesh code.
    Delimiter String:
    Specify a delimiter string which should be used as delimiters in the mesh code.
    You can leave this parameter blank if you don't need to delimit the mesh code.

Parameters:
- DELIMITER =
- MESHCODE_ATTR =
- MESH_TYPE =

Input (input)
    -> Tester
Tester
    BOOL_OP = OR
    TEST_CLAUSE = TEST 0 < @Evaluate(@NumCoords())
    TEST_MODE = Automatic
    PASSED -> ParameterFetcher
    FAILED -> <Rejected> (output)
ParameterFetcher
    ATTR_LIST = jpmeshcodeextractor.meshtype {$(MESH_TYPE)} jpmeshcodeextractor.delimiter {$(DELIMITER)}
    -> CoordinateExtractor
CoordinateExtractor
    IND = 0
    X_ATTR = jpmeshcodeextractor.x
    Y_ATTR = jpmeshcodeextractor.y
    Z_DEFAULT = -9999
    -> PythonCaller
PythonCaller
    NEW_ATTRIBUTES = jpmeshcodeextractor.meshcode
    PYTHONSOURCE:
      import fmeobjects

      # 2015-11-30: Improved to avoid unexpected mesh code from an aggregate geometry.
      # 2015-05-28: Added 1/10 subdivided mesh code creation support.

      def extractMeshCode(feature):
          mtype = int(feature.getAttribute('jpmeshcodeextractor.meshtype'))
          delim = feature.getAttribute('jpmeshcodeextractor.delimiter')
          meshAttr = 'jpmeshcodeextractor.meshcode'

          # Get latitude and longitude of the first coordinate of the feature, in milliseconds.
          # 2015-11-30: Replaced FMEFeature.getCoordinate method with the CoordinateExtractor
          # to avoid unexpected coordinate values from an aggregate geometry.
          #coord = feature.getCoordinate(0)
          coord = (float(feature.getAttribute('jpmeshcodeextractor.x')),
              float(feature.getAttribute('jpmeshcodeextractor.y')))
          lat_ms = int(round(coord[1] * 3600000.0))
          lon_ms = int(round(coord[0] * 3600000.0))

          # Primary Mesh Code
          a, b = lat_ms // 2400000, int(coord[0]) - 100
          meshCode = '%02d%02d' % (a, b)
          if mtype == 1:
              feature.setAttribute(meshAttr, meshCode)
              return
          lat_ms -= a * 2400000
          lon_ms -= (b + 100) * 3600000

          # Secondary Mesh Code
          c, d = lat_ms // 300000, lon_ms // 450000
          meshCode = '%s%s%d%d' % (meshCode, delim, c, d)
          if mtype == 2:
              feature.setAttribute(meshAttr, meshCode)
              return
          lat_ms %= 300000
          lon_ms %= 450000

          # Tertiary Mesh Code
          e, f = lat_ms // 30000, lon_ms // 45000
          meshCode = '%s%s%d%d' % (meshCode, delim, e, f)
          if mtype == 3:
              feature.setAttribute(meshAttr, meshCode)
              return
          lat_ms %= 30000
          lon_ms %= 45000

          if mtype == 10:
              # 1/10 Subdivided Mesh Code
              x, y = lat_ms // 3000, lon_ms // 4500
              meshCode = '%s%s%d%d' % (meshCode, delim, x, y)
              feature.setAttribute(meshAttr, meshCode)
          else:
              # 1/2 Subdivided Mesh Code
              div = (1 if lon_ms < 22500 else 2) + (0 if lat_ms < 15000 else 2)
              meshCode = '%s%s%d' % (meshCode, delim, div)
              if mtype == 4:
                  feature.setAttribute(meshAttr, meshCode)
                  return
              lat_ms %= 15000
              lon_ms %= 22500

              # 1/4 Subdivided Mesh Code
              div = (1 if lon_ms < 11250 else 2) + (0 if lat_ms < 7500 else 2)
              meshCode = '%s%s%d' % (meshCode, delim, div)
              if mtype == 5:
                  feature.setAttribute(meshAttr, meshCode)
                  return
              lat_ms %= 7500
              lon_ms %= 11250

              # 1/8 Subdivided Mesh Code
              div = (1 if lon_ms < 5625 else 2) + (0 if lat_ms < 3750 else 2)
              meshCode = '%s%s%d' % (meshCode, delim, div)
              feature.setAttribute(meshAttr, meshCode)
    PYTHONSYMBOL = extractMeshCode
    -> BulkAttributeRenamer
BulkAttributeRenamer
    ATTRCHOICE = Selected Attributes
    ATTRLIST = jpmeshcodeextractor.meshcode
    PATTERN_ACTION_DISP = Regular Expression Replace
    REPLACE_PATTERN = .*
    REPLACE_STR = $(MESHCODE_ATTR)
    -> BulkAttributeRemover
BulkAttributeRemover
    ATTR_EXP = jpmeshcodeextractor.
    -> Output (output)
Output (output)
<Rejected> (output)

FME custom transformer JpMeshCodeReplacer
Replaces geometry of input feature with a rectangular polygon or a point which represents the location of Japanese standard mesh code stored in an attribute. 
    This transformer determines mesh type automatically based on format of the mesh code. 
    The mesh type (a number) will be stored in an attribute whose name was specified to the "Mesh Type Attribute" parameter.
    Mesh Type | Description | Mesh Code Format 
    1 | Primary Standard Mesh | AABB 
    2 | Secondary Standard Mesh | AABB<delim>CD 
    3 | Tertiary Standard Mesh | AABB<delim>CD<delim>EF 
    4 | 1/2 Subdivided Mesh | AABB<delim>CD<delim>EF<delim>G 
    5 | 1/4 Subdivided Mesh | AABB<delim>CD<delim>EF<delim>G<delim>H 
    6 | 1/8 Subdivided Mesh | AABB<delim>CD<delim>EF<delim>G<delim>H<delim>I 
    10 | 1/10 Subdivided Mesh | AABB<delim>CD<delim>EF<delim>XY or AABB<delim>CD<delim>EF<delim>X<delim>Y 
    By default, the transformer replaces a 10 digits mesh code with a 1/4 subdivided mesh. It will be replaced with a 1/10 subdivided mesh only if you set "Yes" to the "10 Digits Code to 1/10 Subdivided Mesh" parameter. 
    The mesh code string can contain delimiter strings (e.g. "54382345", "5438 23 45", "5438-23-45-1-2-3"), but any delimiter must not contain digits. 
    If format of the mesh code is invalid, the feature will be output from the <Rejected> port.
    Note: Unavoidable slight computational errors caused by calculation for floating point numbers may occur in the resulting coordinate values. Consider applying the CoordinateRounder or something similar operations to absorb such errors if necessary.
Parameters
    Mesh Code Attribute:
    Select an existing attribute which is storing mesh code.
    Geometry Type:
    If you choose "Polygon", the geometry will be replaced with a rectangular polygon representing the mesh.
    If you choose "Point - Center", the geometry will be replaced with a point at the center of the mesh.
    If you choose "Point - Corner", the geometry will be replaced with a point at the south-west corner of the mesh.
    Mesh Type Attribute:
    Specify an attribute name that should store the mesh type (1 - 6, 10).
    10 Digits Code to 1/10 Subdivided Mesh:
    By default, the transformer replaces a 10 digits mesh code with a 1/4 subdivided mesh. If you set "Yes" to this parameter, the code will be replaced with a 1/10 subdivided mesh.

Parameters:
- CREATE_ONE_TENTH_SUBMESH =
- GEOM_TYPE =
- MESHCODE_ATTR =
- MESHTYPE_ATTR =

Input (input)
    -> ParameterFetcher
ParameterFetcher
    ATTR_LIST = jpmeshcodereplacer.geomtype {$(GEOM_TYPE)} jpmeshcodereplacer.createOneTenthSubMesh {$(CREATE_ONE_TENTH_SUBMESH)} jpmeshcodereplacer.meshtype_attr {$(MESHTYPE_ATTR)}
    -> StringSearcher
Note: StringSearcher [StringSearcher] / Parameters: / Search In: @Value($(MESHCODE_ATTR)) / Regular Expression: ^\D*(\d{4})(\D*([0-7]{2})(\D*(\d\d)(\D*([1-4])(\D*([1-4])(\D*([1-4]))?)?)?)?)?\D*$ / Case Sensitive: No / Matched Result Attribute: jpmeshcodereplacer.unused / Matched Parts Attribute: jpmeshcodereplacer.code
StringSearcher
    CASE = no
    MATCHED_PARTS_ATTR = jpmeshcodereplacer.code
    MATCHED_RESULT_ATTR = jpmeshcodereplacer.unused
    REGEXP = ^\D*(\d{4})(\D*([0-7]{2})(\D*(\d\d)(\D*([1-4])(\D*([1-4])(\D*([1-4]))?)?)?)?)?\D*$
    STRING_TO_SEARCH = @Value($(MESHCODE_ATTR))
    MATCHED -> PythonCaller
    NOT_MATCHED -> Tester
Tester
    BOOL_OP = OR
    TEST_CLAUSE = TEST @Value(jpmeshcodereplacer.createOneTenthSubMesh) = Yes
    TEST_MODE = Automatic
    PASSED -> StringSearcher_2
    FAILED -> <Rejected> (output)
Note: StringSearcher_2 [StringSearcher] / Parameters: / Search In: @Value($(MESHCODE_ATTR)) / Regular Expression: ^\D*(\d{4})(\D*([0-7]{2})(\D*(\d\d)(\D*(\d)(\D*(\d))?)?)?)?\D*$ / Case Sensitive: No / Matched Result Attribute: jpmeshcodereplacer.unused / Matched Parts Attribute: jpmeshcodereplacer.code
StringSearcher_2
    CASE = no
    MATCHED_PARTS_ATTR = jpmeshcodereplacer.code
    MATCHED_RESULT_ATTR = jpmeshcodereplacer.unused
    REGEXP = ^\D*(\d{4})(\D*([0-7]{2})(\D*(\d\d)(\D*(\d)(\D*(\d))?)?)?)?\D*$
    STRING_TO_SEARCH = @Value($(MESHCODE_ATTR))
    MATCHED -> PythonCaller
    NOT_MATCHED -> <Rejected> (output)
PythonCaller
    PYTHONSOURCE:
      # 2017-04-05 Takashi Iijima: Minor change regarding Mesh Type Attribute parameter.
      # 2017-04-03 Takashi Iijima: Modify the procedure to collect code elements from the list.
      # 2015-11-27 Takashi Iijima: Reduced computational error in floating point calculation.
      # 2015-05-28 Takashi Iijima: Added 1/10 subdivided mesh creation support.
      import fmeobjects

      def replaceJpMesh(feature):
          code, i = [], 0
          while True:
              c = feature.getAttribute('jpmeshcodereplacer.code{%d}' % i)
              if not c:
                  break
              code.append(int(c))
              i += 2
          meshType = len(code)
          attr = feature.getAttribute('jpmeshcodereplacer.meshtype_attr')
          if attr:
              feature.setAttribute(attr, meshType)

          # Primary Standard Mesh
          lat_ms = (code[0] // 100) *2400000
          lon_ms = (code[0] % 100 + 100) * 3600000
          if meshType == 1:
              replaceJpMeshSub(feature, lat_ms, lon_ms, 3600000, 2400000)
              return

          # Secondary Standard Mesh
          lat_ms += (code[1] // 10) * 300000
          lon_ms += (code[1] % 10) * 450000
          if meshType == 2:
              replaceJpMeshSub(feature, lat_ms, lon_ms, 450000, 300000)
              return

          # Tertiary Standard Mesh
          lat_ms += (code[2] // 10) * 30000
          lon_ms += (code[2] % 10) * 45000
          if meshType == 3:
              replaceJpMeshSub(feature, lat_ms, lon_ms, 45000, 30000)
              return

          if meshType == 5 and feature.getAttribute('jpmeshcodereplacer.createOneTenthSubMesh') == 'Yes':
              # 1/10 Subdivided Mesh (2015-05-28)
              lat_ms += code[3] * 3000
              lon_ms += code[4] * 4500
              replaceJpMeshSub(feature, lat_ms, lon_ms, 4500, 3000)
              if attr:
                  feature.setAttribute(attr, 10)
          else:
              # 1/2 Subdivided Mesh
              lat_ms += (15000 if 2 < code[3] else 0)
              lon_ms += (22500 if code[3] % 2 == 0 else 0)
              if meshType == 4:
                  replaceJpMeshSub(feature, lat_ms, lon_ms, 22500, 15000)
                  return

              # 1/4 Subdivided Mesh
              lat_ms += (7500 if 2 < code[4] else 0)
              lon_ms += (11250 if code[4] % 2 == 0 else 0)
              if meshType == 5:
                  replaceJpMeshSub(feature, lat_ms, lon_ms, 11250, 7500)
                  return

              # 1/8 Subdivided Mesh
              lat_ms += (3750 if 2 < code[5] else 0)
              lon_ms += (5625 if code[5] % 2 == 0 else 0)
              replaceJpMeshSub(feature, lat_ms, lon_ms, 5625, 3750)

      def replaceJpMeshSub(feature, lat, lon, w, h):
          scale = 3600000.0
          geomType = feature.getAttribute('jpmeshcodereplacer.geomtype')
          geom = None
          if geomType == 'Point_Corner':
              geom = fmeobjects.FMEPoint(lon / scale, lat / scale)
          elif geomType == 'Point_Center':
              geom = fmeobjects.FMEPoint((lon + w * 0.5) / scale, (lat + h * 0.5) / scale)
          else: # Polygon
              coords = [(lon, lat), (lon + w, lat), (lon + w, lat + h), (lon, lat + h), (lon, lat)]
              boundary = fmeobjects.FMELine([(x / scale, y / scale) for x, y in coords])
              geom = fmeobjects.FMEPolygon(boundary)
          feature.setGeometry(geom)
    PYTHONSYMBOL = replaceJpMesh
    -> AttributeRemover
AttributeRemover
    LIST_ATTRS = jpmeshcodereplacer.code{}
    REMOVE_ATTRS = jpmeshcodereplacer.createOneTenthSubMesh,jpmeshcodereplacer.geomtype,jpmeshcodereplacer.meshtype_attr,jpmeshcodereplacer.unused
    -> Output (output)
<Rejected> (output)
Note: Expose Mesh Type Attribute
BoundsExtractor [off]
    XMIN = $(MESHTYPE_ATTR)
    -> Output (output)
Output (output)
