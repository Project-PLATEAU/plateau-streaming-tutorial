FME workspace s1_基盤地図情報DEMのGeoTIFF変換.fmw

Parameters:
- DEST_GETOTIFF_EL_ROOT_FODER =
- LOG_FILE =
- SOURCE_FGD_DEM_ZIP =

Writers:
- GEOTIFF_1: GEOTIFF to $(DEST_GETOTIFF_EL_ROOT_FODER)

Creator
    GEOMTYPE = Geometry Object
    NUM = 1
    CREATED -> FilePathExtractor [Initiator]
FilePathExtractor
    EXTRACT_ZIP_FILES = No
    SOURCE_DATASET = $(SOURCE_FGD_DEM_ZIP)
    -> AttributeManager
AttributeManager
    ATTR_TABLE:
      REMOVE _path_windows
      REMOVE _path_filename
      RENAME_SET_VALUE _path_rootname > _dest_rootname
      REMOVE _path_extension
      REMOVE _path_directory_unix
      REMOVE _path_directory_windows
    -> FeatureReader [INITIATOR]
FeatureReader
    ATTRIBUTES = DEMRASTER,"fid,devDate,lfSpanFr,lfSpanTo,orgGILvl,orgMDId,mesh,type,fgd_dem_type"
    ATTR_ACCUM_MODE = Merge Initiator and Result
    ATTR_CONFLICT_RES = Use Result
    ATTR_IGNORE_NULLS = No
    COMBINE_GEOM = Use Result
    DATASET = @Value(_path_unix)
    FORMAT = JP_FGD_DEM2
    INTERACT = NONE
    JP_FGD_DEM2_VALIDATE_SCHEMA_LOCATION = Yes
    OUTPUT_FEATURES_DISPLAY = Schema and Data Features
    DEMRASTER -> RasterInterpretationCoercer
RasterInterpretationCoercer
    COLOR_TO_NUMERIC = Bounded cast
    INTERPRETATION = Real32
    NUMERIC_TO_NUMERIC = Bounded cast
    -> StringCaseChanger
StringCaseChanger
    ATTRCHOICE = Selected Attributes
    ATTRLIST = fgd_dem_type
    CHANGE_TYPE = lowercase
    -> Tester
Tester
    BOOL_OP = OR
    COMPOSITE_TEST = 1
    TEST_CLAUSE = CASE_INSENSITIVE_TEST @Value(fgd_dem_type) BEGINS_WITH dem10
    TEST_MODE = TEST
    PASSED -> Raster1 (writer GEOTIFF_1)
    FAILED -> RasterMosaicker
RasterMosaicker
    ACCUM_ATTRS_NAME = Use Attributes From One Feature
    GROUP_BY = _dest_rootname
    INTERPOLATION_TYPE_NAME = Nearest Neighbor
    MERGE_PALETTES_NAME = Yes
    NODATA_OVERWRITE = No
    OVERLAPPING_VALUES = last
    SNAPPING_TYPE_NAME = Resample
    -> Raster1 (writer GEOTIFF_1)
Raster1 (writer GEOTIFF_1)

FME custom transformer FilePathExtractor
Extracts all the file paths which can be accessed by a string specified through a Filename (Multiple) type user parameter, and outputs features each of which has attributes storing the file path, file name, directory path etc.
If the source string contains a zip file path which is specified with the Select Multiple Folders/Files function (called "Advanced Browser" in the old days), the transformer considers it as a folder-like thing, will unzip it automatically and output features for each extracted file.
A zip file directly specified with the standard Select Files dialog will also be unzipped by default. However, you can set No to the Extract Zip Files parameter not to unzip them.

Parameters:
- EXTRACT_ZIP_FILES =
- SOURCE_DATASET =

Initiator (input)
    -> ParameterFetcher
ParameterFetcher
    ATTR_LIST = __source_dataset $(SOURCE_DATASET)
    -> PythonCaller
PythonCaller
    HIDE_ATTRIBUTES = __source_dataset
    NEW_ATTRIBUTES = __path_unix
    PYTHONSOURCE:
      import fme
      import fmeobjects
      import shlex
      class PathElementExtractor(object):
          def __init__(self):
              pass

          def input(self, feature):
              dataset = feature.getAttribute('__source_dataset')
              feature.removeAttribute('__source_dataset')
              if dataset.startswith('"'):
                  for path in shlex.split(dataset.replace('""', '"')):
                      feature.setAttribute('__path_unix', path.replace('\\', '/'))
                      self.pyoutput(feature)
              else:
                  feature.setAttribute('__path_unix', dataset.replace('\\', '/'))
                  self.pyoutput(feature)

          def close(self):
              pass
    PYTHONSYMBOL = PathElementExtractor
    -> StringSearcher
StringSearcher
    CASE = no
    MATCHED_PARTS_ATTR = _sub
    REGEXP = ^(.+\.zip)\[(.+)\]$
    STRING_TO_SEARCH = @Value(__path_unix)
    MATCHED -> AttributeManager
    NOT_MATCHED -> FilenamePartExtractor
AttributeManager
    ATTR_TABLE:
      SET_TO __dirpath = FME_CONDITIONAL:DEFAULT_VALUE'@Value(_sub{0}.part)'BOOL_OP;OR;COMPOSITE_TEST;1;CASE_INSENSITIVE_TEST @Value(_sub{1}.part) BEGINS_WITH **/'@Value(_sub{0}.part)/**/'FME_NUM_CONDITIONS2___
      SET_TO __path_filter = @ReplaceRegEx(@Value(_sub{1}.part),"(\*\*/)?(.+)",\2)
      REMOVE __path_unix
      REMOVE _sub{}.part
      REMOVE _sub{}.startIndex
    -> FeatureReader [INITIATOR]
FilenamePartExtractor
    DIRPATH_ATTR = __dirpath
    FULLNAME_ATTR = __path_filter
    SRC_ATTR = @Value(__path_unix)
    -> FeatureReader [INITIATOR]
FeatureReader
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Merge Initiator and Result
    ATTR_CONFLICT_RES = Use Result
    COMBINE_GEOM = Use Initiator
    DATASET = @Value(__dirpath)
    FORMAT = PATH
    OUTPUT_FEATURES_DISPLAY = Data Features
    PATH_GLOB_PATTERN = @Value(__path_filter)
    PATH_NO_EMPTY_PROPERTIES = YES
    PATH_RECURSE_DIRECTORIES = NO
    PATH_RETRIEVE_FILE_PROPERTIES = NO
    PATH_TYPE = FILE
    PATH -> Tester
Tester
    BOOL_OP = COMPOSITE
    COMPOSITE_TEST = 1 AND 2
    TEST_CLAUSE:
      CASE_INSENSITIVE_TEST @Value(path_extension) = zip
      CASE_INSENSITIVE_TEST $(EXTRACT_ZIP_FILES) = Yes
    TEST_MODE = CASE_INSENSITIVE_TEST
    PASSED -> FeatureReader_3 [INITIATOR]
    FAILED -> AttributeManager_2
FeatureReader_3
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Merge Initiator and Result
    ATTR_CONFLICT_RES = Use Result
    COMBINE_GEOM = Use Initiator
    DATASET = @Value(path_unix)/**\/
    FORMAT = PATH
    OUTPUT_FEATURES_DISPLAY = Data Features
    PATH_GLOB_PATTERN = *
    PATH_NO_EMPTY_PROPERTIES = YES
    PATH_RECURSE_DIRECTORIES = YES
    PATH_RETRIEVE_FILE_PROPERTIES = NO
    PATH_TYPE = FILE
    PATH -> AttributeManager_2
AttributeManager_2
    ATTR_TABLE:
      RENAME_SET_VALUE path_unix > _path_unix
      RENAME_SET_VALUE path_windows > _path_windows
      RENAME_SET_VALUE path_filename > _path_filename
      RENAME_SET_VALUE path_rootname > _path_rootname
      RENAME_SET_VALUE path_extension > _path_extension
      RENAME_SET_VALUE path_directory_unix > _path_directory_unix
      RENAME_SET_VALUE path_directory_windows > _path_directory_windows
      REMOVE __path_unix
      REMOVE __dirpath
      REMOVE __path_filter
      REMOVE path_filesize
      REMOVE path_ownername
      REMOVE path_readonly
      REMOVE path_modified_date
      REMOVE path_created_date
      REMOVE path_accessed_date
      REMOVE path_type
      REMOVE fme_geometry{}
    -> Output (output)
Output (output)
