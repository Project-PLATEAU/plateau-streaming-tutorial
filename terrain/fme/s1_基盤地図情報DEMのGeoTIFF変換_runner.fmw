FME workspace s1_基盤地図情報DEMのGeoTIFF変換_runner.fmw

Parameters:
- DEST_GOTIFF_ROOT_DIR =
- FGD_DEM_DOWNLOADS_DIR =
- LOG_FOLDER =
- MAX_PROC =
- MAX_TO_BATCH =

Readers:
- PATH_1: PATH from $(FGD_DEM_DOWNLOADS_DIR)

Note: PATH: downloads [PATH]
PATH (reader PATH_1)
    attributes: path_unix buffer, path_windows buffer, path_rootname buffer, path_filename buffer, path_extension buffer, path_filesize number(20,0), path_ownername buffer, path_readonly logical, path_modified_date datetime, path_created_date datetime, path_accessed_date datetime, path_directory_unix buffer, path_directory_windows buffer, path_type char(10)
    -> AttributeSplitter
AttributeSplitter
    ATTR_NAME = path_rootname
    DELIMITER = -
    DROP_EMPTY_PARTS = No
    LIST_NAME = _list
    TRIM_OPTION = Both
    -> ListIndexer
ListIndexer
    INDEX = -1
    LIST_ATTR = _list{}
    -> AttributeManager
AttributeManager
    ATTR_TABLE:
      SET_TO _dem_type = @LowerCase(@Value(_list))
      REMOVE path_windows
      REMOVE path_filename
      REMOVE path_extension
      REMOVE path_filesize
      REMOVE path_ownername
      REMOVE path_readonly
      REMOVE path_modified_date
      REMOVE path_created_date
      REMOVE path_accessed_date
      REMOVE path_directory_unix
      REMOVE path_directory_windows
      REMOVE path_type
      REMOVE _list{}
      REMOVE _list
    -> WorkspaceRunner
WorkspaceRunner
    BLOCKING = No
    MAX_PROC = $(MAX_PROC)
    MAX_TO_BATCH = $(MAX_TO_BATCH)
    WORKSPACE_FILE = $(FME_MF_DIR)s1_基盤地図情報DEMのGeoTIFF変換.fmw
    WORKSPACE_PARAMETERS = SOURCE_FGD_DEM_ZIP,@Value(path_unix),DEST_GETOTIFF_EL_ROOT_FODER,$(DEST_GOTIFF_ROOT_DIR),LOG_FILE,$(LOG_FOLDER)/@Value(path_rootname).log
